(command "netload" "C:\\Users\\mrl9000\\OneDrive - INFRABEL\\Documents\\cSharp\\00_Acad\\00_PP\\CmdTools\\bin\\Debug\\CmdTools.dll")
(command "netload" "C:\\Users\\mrl9000\\OneDrive - INFRABEL\\Documents\\cSharp\\00_Acad\\00_PP\\DevTools\\bin\\Debug\\\DevTools.dll")
(command "netload" "C:\\Users\\mrl9000\\OneDrive - INFRABEL\\Documents\\cSharp\\00_Acad\\00_PP\\EplanPlugin\\bin\\Debug\\EplanPlugin.dll")
(command "netload" "C:\\Users\\mrl9000\\OneDrive - INFRABEL\\Documents\\cSharp\\00_Acad\\00_PP\\LezenEnSchrijvenLegende\\bin\\Debug\\LezenEnSchrijvenLegende.dll")
(command "netload" "C:\\Users\\mrl9000\\OneDrive - INFRABEL\\Documents\\cSharp\\00_Acad\\00_PP\\PlotPdf\\bin\\Debug\\PlotPdf.dll")
(command "netload" "C:\\Users\\mrl9000\\OneDrive - INFRABEL\\Documents\\cSharp\\00_Acad\\00_PP\\TitleBlockManager\\bin\\Debug\\TitleBlockManager.dll")
(command "netload" "C:\\Users\\mrl9000\\OneDrive - INFRABEL\\Documents\\cSharp\\00_Acad\\00_PP\\VerdeelnetKeten\\bin\\Debug\\VerdeelnetKeten.dll")
(command "netload" "C:\\Users\\mrl9000\\OneDrive - INFRABEL\\Documents\\cSharp\\00_Acad\\00_PP\\BlockUpdate\\bin\\Debug\\BlockUpdate.dll")
;(command "netload" "C:\\Users\\mrl9000\\OneDrive - INFRABEL\\Documents\\cSharp\\02_Oefeningen\\RunOnStartUp\\bin\\Debug\\RunOnStartUp.dll")

	(load "C:\\ProgramData\\Autodesk\\ApplicationPlugins\\PpNwDo.bundle\\Contents\\AutoLisp\\ActivateDrawBox.lsp")
	(load "C:\\ProgramData\\Autodesk\\ApplicationPlugins\\PpNwDo.bundle\\Contents\\AutoLisp\\BatchWBLOCK.lsp")
	(load "C:\\ProgramData\\Autodesk\\ApplicationPlugins\\PpNwDo.bundle\\Contents\\AutoLisp\\GatteV2.lsp")
	(load "C:\\ProgramData\\Autodesk\\ApplicationPlugins\\PpNwDo.bundle\\Contents\\AutoLisp\\Tellers.lsp")
	
	


;; voorbeeld pad
;;(command "netload" "C:\\ProgramData\\Autodesk\\ApplicationPlugins\\VvdkNwDo.bundle\\Contents\\Plugin\\.dll")
;;(load "C:\\ProgramData\\Autodesk\\ApplicationPlugins\\VvdkNwDo.bundle\\Contents\\AutoLisp\\.lsp")




C:\Users\mrl9000\OneDrive - INFRABEL\Documents\cSharp\00_Acad\00_PP
